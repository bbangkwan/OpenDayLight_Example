module example {
    yang-version 1;
    namespace "urn:opendaylight:params:xml:ns:yang:example";
    prefix "example";

    revision "2015-01-05" {
        description "Initial revision of example model";
    }

    rpc rpc-test{
        input{
            leaf firstInput{
                type string;
            }
            leaf secondInput{
                type int32;
            }
        }

        output{
            leaf testOutput{
                type string;
            }
        }
    }
}
